A DEFINITIONS AUTOMATIC TAGS ::= BEGIN
IMPORTS Beta FROM B;
Leaf ::= INTEGER (0..255)
Alpha ::= SEQUENCE { beta Beta }
END
B DEFINITIONS AUTOMATIC TAGS ::= BEGIN
IMPORTS Leaf FROM A;
Beta ::= SEQUENCE { leaf Leaf }
END
