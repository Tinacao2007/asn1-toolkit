C7 DEFINITIONS AUTOMATIC TAGS ::= BEGIN
Named ::= BIT STRING { first(0), fourth(3) } (SIZE(1..8))
Fixed ::= BIT STRING { first(0) } (SIZE(16))
Stamp ::= UTCTime
Sparse ::= INTEGER (1..3|8|15,...)
StampSized ::= UTCTime (SIZE(13))
END
