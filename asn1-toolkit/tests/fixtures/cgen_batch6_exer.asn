X6 DEFINITIONS XER INSTRUCTIONS AUTOMATIC TAGS ::= BEGIN
Record ::= SEQUENCE { flag [ATTRIBUTE] BOOLEAN, count INTEGER (0..7), text UTF8String }
Binary ::= [BASE64] OCTET STRING
List ::= [LIST] SEQUENCE OF INTEGER (0..7)
TextBool ::= [TEXT] BOOLEAN
Number ::= [USE-NUMBER] ENUMERATED { red, blue }
END
